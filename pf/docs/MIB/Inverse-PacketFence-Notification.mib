INVERSE-PACKETFENCE-NOTIFICATION-MIB DEFINITIONS ::= BEGIN

IMPORTS
    ifIndex     
       FROM IF-MIB
    enterprises, NOTIFICATION-TYPE
       FROM SNMPv2-SMI;

inverse         OBJECT IDENTIFIER ::= { enterprises 29464 }

inversePacketFenceNotificationMIB MODULE-IDENTITY
  LAST-UPDATED "201003261700Z"
  ORGANIZATION "Inverse inc."
  CONTACT-INFO
    "Inverse
     email: support@inverse.ca"
  DESCRIPTION
    "Definition of PacketFence SNMP Notification"
  ::= { inverse 1 }

packetFenceRecalculateVLANNotification NOTIFICATION-TYPE
  OBJECTS { ifIndex, connectionType }
  STATUS current
  DESCRIPTION
    "This notification is generated when the VLAN assigned to
     the specified switch port should be recalculated and
     (possibly) correctly re-assigned."
  ::= { inversePacketFenceNotificationMIB 1 }

packetFenceDesAssociateNotification NOTIFICATION-TYPE
  OBJECTS { mac, connectionType }
  STATUS current
  DESCRIPTION
    "This notification is generated when the MAC
     should be des-associated (WIFI)."
  ::= { inversePacketFenceNotificationMIB 2 }
END
